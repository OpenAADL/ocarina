Custom_Service DEFINITIONS ::= BEGIN

	Request ::= SEQUENCE {
		a Integer,
		b PrintableString,
		proc BOOLEAN
	}

	Response ::= SEQUENCE {
		appended INTEGER,
		length REAL,
		pose geometry_msgs/Pose
	}

END
