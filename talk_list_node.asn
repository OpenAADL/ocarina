InternalState DEFINITIONS ::= BEGIN
	Parameters ::= SET {
		stringName STRING DEFAULT "ciao",
		testReal REAL DEFAULT 0,

		traj SET {
			test1 REAL DEFAULT 1.0,
			test2 INTEGER DEFAULT 2
		}
	}

	Variables ::= SET {
		publisherFrequency REAL DEFAULT 0
	}

END
