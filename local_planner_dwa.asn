InternalState DEFINITIONS ::= BEGIN
    Costmap2D ::= OBJECT
    Parameters ::= SET {
        robotConfiguration SET {
            acc_lim_x REAL DEFAULT 2.5,
            acc_lim_y REAL DEFAULT 2.5,
            acc_lim_th REAL DEFAULT 3.2,
            max_trans_vel REAL DEFAULT 0.55,
            min_trans_vel REAL DEFAULT 0.1,
            max_vel_x REAL DEFAULT 0.55,
            min_vel_x REAL DEFAULT 0.0,
            max_vel_y REAL DEFAULT 0.1,
            min_vel_y REAL DEFAULT -0.1,
            max_rot_vel REAL DEFAULT 1.0,
            min_rot_vel REAL DEFAULT 0.4
        },
        goalTolerance SET {
            yaw_goal_tolerance REAL DEFAULT 0.05,
            xy_goal_tolerance REAL DEFAULT 0.10,
            latch_xy_goal_tolerance BOOLEAN DEFAULT FALSE
        },
        forwardSimulation SET {
            sim_time REAL DEFAULT 1.7,
            sim_granularity REAL DEFAULT 0.025,
            vx_samples INTEGER DEFAULT 3,
            vy_samples INTEGER DEFAULT 10,
            vth_samples INTEGER DEFAULT 20,
            controller_frequency REAL DEFAULT 20.0
        },
        -- trajectoryScoring/path_distance_bias
        trajectoryScoring SET {
            path_distance_bias REAL DEFAULT 32.0,
            goal_distance_bias REAL DEFAULT 24.0,
            occdist_scale REAL DEFAULT 0.01,
            forward_point_distance REAL DEFAULT 0.325,
            stop_time_buffer REAL DEFAULT 0.2,
            scaling_speed REAL DEFAULT 0.25,
            max_scaling_factor REAL DEFAULT 0.2
        },
        oscillation_reset_dist REAL DEFAULT 0.05,
        prune_plan BOOLEAN DEFAULT true
    }
    Variables ::= SET {
        --WIP
        costmap Costmap2D,
        mapFrame STRING DEFAULT "map",
        current_path nav_msgs/Path,
        current_goal geometry_msgs/Pose
    }
END
