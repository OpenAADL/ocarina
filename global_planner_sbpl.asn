InternalState DEFINITIONS ::= BEGIN
    Costmap2D ::= OBJECT

    Parameters ::= SET {
      
        replan BOOLEAN DEFAULT FALSE,
        starting_epsilon REAL,
        ending_epsilon REAL,
       
        dimensions INTEGER DEFAULT 3,
        motPrimString STRING DEFAULT "generated_primitives.txt",

        vehicleParams SET {
            robotShape STRING DEFAULT "circular",
            robot_width REAL DEFAULT 1.5,
            robot_length REAL DEFAULT 3.5,
            v_max REAL DEFAULT 2.0,
            omega_max REAL DEFAULT 1.5708
        },
        planningSetup SET {
            planner_type STRING DEFAULT "adstar",
            allocated_time REAL DEFAULT 10.0,
            initial_epsilon REAL DEFAULT 20.0,
            epsilon_decrease_step REAL DEFAULT 0.5
        },
        mapParameters SET {
            resolutionTolerance REAL DEFAULT 0.0001,
            obsthresh INTEGER DEFAULT 254,
            cost_inscribed_thresh INTEGER DEFAULT 253,
            cost_possibly_circumscribed_thresh INTEGER DEFAULT 128
        }
    }
    Variables ::= SET {

        costmap Costmap2D,
        mapFrame STRING DEFAULT "map",
        epsilon REAL,
        flags SET {
            new_goal BOOLEAN DEFAULT FALSE,
            new_plan BOOLEAN DEFAULT FALSE,
            new_costmap BOOLEAN DEFAULT FALSE
        }
        
    }
END
